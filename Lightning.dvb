Attribute VB_Name = "frmEditMast"
Attribute VB_Base = "0{9300B275-D942-492D-A0F4-15334B151570}{93522300-DD62-4004-9A84-E0CE07DC0AD7}"
Attribute VB_GlobalNameSpace = False
Attribute VB_Creatable = False
Attribute VB_PredeclaredId = True
Attribute VB_Exposed = False
Attribute VB_TemplateDerived = False
Attribute VB_Customizable = False
Option Explicit

Private Sub cmbCancel_Click()
frmEditMast.Hide
frmMain.Show
End Sub

Private Sub cmbLocation_Click()
Call modProcedures.edit_mast_location
End Sub

Private Sub UserForm_Activate()
Dim intRow As Integer

intRow = frmMain.lbxMasts.ListIndex

txbID.Value = frmMain.lbxMasts.Column(0, intRow)
txbHeight.Value = frmMain.lbxMasts.Column(1, intRow)

End Sub

Attribute VB_Name = "frmMain"
Attribute VB_Base = "0{00619EA3-4CFF-4EFE-A7DC-DE43BF3A41DA}{19F6A993-DE65-4D60-A416-424A3A8112DE}"
Attribute VB_GlobalNameSpace = False
Attribute VB_Creatable = False
Attribute VB_PredeclaredId = True
Attribute VB_Exposed = False
Attribute VB_TemplateDerived = False
Attribute VB_Customizable = False
Option Explicit

Private Sub cmbClose_Click()
frmMain.Hide
End Sub

Private Sub cmbDeleteMast_Click()
Call modProcedures.delete_mast
End Sub

Private Sub cmbDeleteWire_Click()
Call modProcedures.delete_wire
End Sub

Private Sub cmbEditMast_Click()
frmMain.Hide
frmEditMast.Show
End Sub

Private Sub cmbNewMast_Click()
If pubDWGScale = 0 Then
    MsgBox "You must set the project scale first.", vbOKOnly, "Error"
Else
    frmMain.Hide
    frmNewMast.Show
End If
End Sub

Private Sub cmbNewWire_Click()
frmMain.Hide
frmNewWire.Show
End Sub

Private Sub cmbProjectApply_Click()
Call modProcedures.write_project_data
End Sub

Private Sub cmbProjectReset_Click()
Call modProcedures.reset_project_data
End Sub

Private Sub txbClient_Change()
cmbProjectApply.Enabled = True
cmbProjectReset.Enabled = True
End Sub

Private Sub txbProjectName_Change()
cmbProjectApply.Enabled = True
cmbProjectReset.Enabled = True
End Sub

Private Sub txbScale_Change()
cmbProjectApply.Enabled = True
cmbProjectReset.Enabled = True
End Sub

Private Sub UserForm_Activate()
Call modProcedures.load_mast_data
Call modProcedures.load_wire_data
End Sub

Private Sub UserForm_Initialize()
Call modVariables.set_variables
Call modProcedures.get_project_data

txbProjectName.Value = pubProjectName
txbClient.Value = pubClient
txbScale.Value = pubDWGScale

cmbProjectApply.Enabled = False
cmbProjectReset.Enabled = False
End Sub

Attribute VB_Name = "frmNewMast"
Attribute VB_Base = "0{B8923875-1723-4AE6-8C6D-AE913BA82E06}{F102350E-ADB4-41AF-A0E8-75104F29D756}"
Attribute VB_GlobalNameSpace = False
Attribute VB_Creatable = False
Attribute VB_PredeclaredId = True
Attribute VB_Exposed = False
Attribute VB_TemplateDerived = False
Attribute VB_Customizable = False
Option Explicit

Private Sub cmbClose_Click()
frmNewMast.Hide
frmMain.Show
End Sub

Private Sub cmbLocation_Click()
Call modProcedures.add_mast
End Sub

Private Sub txbHeight_Change()
If txbHeight.Value > Empty Then
    If txbID.Value > Empty Then
        cmbLocation.Enabled = True
    End If
Else
    cmbLocation.Enabled = False
End If
End Sub

Private Sub txbID_Change()
If txbID.Value > Empty Then
    If txbHeight.Value > Empty Then
        cmbLocation.Enabled = True
    End If
Else
    cmbLocation.Enabled = False
End If
End Sub

Private Sub UserForm_Activate()
If txbID.Value = Empty Then
    cmbLocation.Enabled = False
ElseIf txbHeight.Value = Empty Then
    cmbLocation.Enabled = False
End If
End Sub

Attribute VB_Name = "frmNewWire"
Attribute VB_Base = "0{173334AE-66BD-46E0-A05C-2AAB29ACDBBB}{7990DEB3-5145-4D99-8B1A-8DB4B9C1E80F}"
Attribute VB_GlobalNameSpace = False
Attribute VB_Creatable = False
Attribute VB_PredeclaredId = True
Attribute VB_Exposed = False
Attribute VB_TemplateDerived = False
Attribute VB_Customizable = False
Option Explicit

Private Sub cmbClose_Click()
frmNewWire.Hide
frmMain.Show
End Sub

Private Sub cmbLocation_Click()
Call modProcedures.add_wire
End Sub

Private Sub txbHeight_Change()
If txbHeight.Value > Empty Then
    If txbID.Value > Empty Then
        cmbLocation.Enabled = True
    End If
Else
    cmbLocation.Enabled = False
End If
End Sub

Private Sub txbID_Change()
If txbID.Value > Empty Then
    If txbHeight.Value > Empty Then
        cmbLocation.Enabled = True
    End If
Else
    cmbLocation.Enabled = False
End If
End Sub

Private Sub UserForm_Activate()
If txbID.Value = Empty Then
    cmbLocation.Enabled = False
ElseIf txbHeight.Value = Empty Then
    cmbLocation.Enabled = False
End If
End Sub

Attribute VB_Name = "modFunctions"
Option Explicit

Public Function XYZDistance(Point1 As Variant, Point2 As Variant) As Double
  'Returns the distance between two points
  Dim dblDist As Double
  Dim dblXSl As Double
  Dim dblYSl As Double
  Dim dblZSl As Double
  Dim varErr As Variant
  On Error GoTo Err_Control
  'Calc distance
  dblXSl = (Point1(0) - Point2(0)) ^ 2
  dblYSl = (Point1(1) - Point2(1)) ^ 2
  dblZSl = (Point1(2) - Point2(2)) ^ 2
  dblDist = Sqr(dblXSl + dblYSl + dblZSl)
  'Return Distance
  XYZDistance = dblDist
Exit_Here:
  Exit Function
Err_Control:
  Select Case Err.Number
  'Add additional Case selections here
    Case Else
    MsgBox Err.Description
    Err.Clear
    Resume Exit_Here
  End Select
End Function

Public Function get_mast(MastID As String)
'this function returns the block reference object
'with the attribute data MastID

Dim i As Integer
Dim MastObj As AcadBlockReference
Dim MastAtt As Variant

'get the mast selection set
Call modProcedures.get_mastSS

'search through selection set for mast
For i = 1 To pubMastSS.Count
    Set MastObj = pubMastSS.Item(i - 1)
    MastAtt = MastObj.GetAttributes
    If MastAtt(0).TextString = MastID Then
        Set get_mast = MastObj
        Exit Function
    End If
Next

End Function

Public Function get_wire(WireID As String)
'this function returns the block reference object
'with the attribute data WireID

Dim i As Integer
Dim WireObj As AcadBlockReference
Dim WireAtt As Variant

'get the wire selection set
Call modProcedures.get_wireSS

'search through selection set for wire
For i = 1 To pubWireSS.Count
    Set WireObj = pubWireSS.Item(i - 1)
    WireAtt = WireObj.GetAttributes
    If WireAtt(0).TextString = WireID Then
        Set get_wire = WireObj
        Exit Function
    End If
Next

End Function

Attribute VB_Name = "modProcedures"
Option Explicit

Public Sub add_mast()
'prompts the user to select the location of a shield mast
'then inserts the ltg_shield_mast block and fills in the
'ID and Height attributes

Dim MastObj As AcadBlockReference
Dim MastAtt As Variant
Dim pt1

frmNewMast.Hide

'get mast location
pt1 = ThisDrawing.Utility.GetPoint(, "Select the location of the shield mast: ")
'insert block
Set MastObj = ThisDrawing.ModelSpace.InsertBlock(pt1, pubBlockPath & "ltg_shield_mast.dwg", pubDWGScale, pubDWGScale, pubDWGScale, 0)
'get attributes
MastAtt = MastObj.GetAttributes
'add mast ID to attribute
MastAtt(0).TextString = frmNewMast.txbID.Value
'add mast height to attribute
MastAtt(1).TextString = frmNewMast.txbHeight.Value
MastObj.Update

'clean up form data
With frmNewMast
    .txbID.Value = Empty
    .txbHeight.Value = Empty
End With

'return to main form
frmMain.Show

End Sub

Public Sub edit_mast_location()
'prompts the user to select the new location of a shield mast
'then inserts the ltg_shield_mast block and fills in the
'ID and Height attributes. The old mast object is then deleted.

Dim MastObj As AcadBlockReference
Dim MastAtt As Variant
Dim pt1
Dim OldMastObj As AcadBlockReference
Dim OldMastAtt As Variant
Dim WireID As String
Dim WireHeight As Double
Dim OldWireObj As AcadBlockReference
Dim OldWireAtt As Variant
Dim Mast1Obj As AcadBlockReference
Dim Mast2Obj As AcadBlockReference
Dim i As Integer

frmEditMast.Hide

'get old mast object and attributes
Set OldMastObj = modFunctions.get_mast(frmMain.lbxMasts.Value)
OldMastAtt = OldMastObj.GetAttributes

'get mast location
pt1 = ThisDrawing.Utility.GetPoint(, "Select the new location of the shield mast: ")

'insert block
Set MastObj = ThisDrawing.ModelSpace.InsertBlock(pt1, pubBlockPath & "ltg_shield_mast.dwg", pubDWGScale, pubDWGScale, pubDWGScale, 0)

'get attributes
MastAtt = MastObj.GetAttributes

'copy attributes from original object
For i = 0 To UBound(OldMastAtt)
    MastAtt(i).TextString = OldMastAtt(i).TextString
Next

'delete old mast object
OldMastObj.Delete

'redraw wires
For i = 2 To 6
    'check to see if there is a wire attached
    If MastAtt(i).TextString > "" Then
        WireID = MastAtt(i).TextString
        'get the wire object and attributes
        Set OldWireObj = modFunctions.get_wire(WireID)
        OldWireAtt = OldWireObj.GetAttributes
        WireHeight = OldWireAtt(1).TextString
        'get wire's mast1 and mast2 objects
        Set Mast1Obj = modFunctions.get_mast(OldWireAtt(2).TextString)
        Set Mast2Obj = modFunctions.get_mast(OldWireAtt(3).TextString)
        'insert new wire
        Call insert_wire(Mast1Obj, Mast2Obj, WireID, WireHeight)
        'delete old wire
        OldWireObj.Delete
    End If
Next

'regen drawing
ThisDrawing.Regen acActiveViewport

'return to edit mast form
frmEditMast.Show

End Sub

Public Sub add_wire()
'prompts the user to select the location of a shield wire
'then inserts the ltg_shield_wire block and fills in the
'ID and Height attributes

Dim Mast1Obj As AcadBlockReference
Dim Mast2Obj As AcadBlockReference
Dim Mast1Att As Variant
Dim Mast2Att As Variant
Dim filtertype(0) As Integer
Dim filterdata(0) As Variant
Dim varPick As Variant
Dim i As Integer

'set dxf data type to "object name"
filtertype(0) = 2

'set dxf data value
filterdata(0) = "ltg_shield_mast"

frmNewWire.Hide

'get first mast
ThisDrawing.Utility.GetEntity Mast1Obj, varPick, vbCr & "Select the first shield mast: "

'get second mast
ThisDrawing.Utility.GetEntity Mast2Obj, varPick, vbCr & "Select the second shield mast: "

'insert wire
Call insert_wire(Mast1Obj, Mast2Obj, frmNewWire.txbID, frmNewWire.txbHeight)

'add wire data to masts
Mast1Att = Mast1Obj.GetAttributes
For i = 2 To 6
    If Mast1Att(i).TextString = "" Then
        Mast1Att(i).TextString = frmNewWire.txbID.Value
        Exit For
    End If
Next
Mast2Att = Mast2Obj.GetAttributes
For i = 2 To 6
    If Mast2Att(i).TextString = "" Then
        Mast2Att(i).TextString = frmNewWire.txbID.Value
        Exit For
    End If
Next

'clean up form data
With frmNewWire
    .txbID.Value = Empty
    .txbHeight.Value = Empty
End With

'regen
ThisDrawing.Regen acActiveViewport

'return to main form
frmMain.Show

End Sub

Public Sub get_mastSS()
'Creates a selection set of all shield mast objects
'in the drawing (objects named "ltg_shield_mast").
'See pubmastss public variable

Dim SSCollection As AcadSelectionSets
Dim SS As AcadSelectionSet
Dim filtertype(0) As Integer
Dim filterdata(0) As Variant
Dim i As Integer

'set dxf data type to "object name"
filtertype(0) = 2
'set dxf data value
filterdata(0) = "ltg_shield_mast"

'search for existing selection set and delete it if found
Set SSCollection = ThisDrawing.SelectionSets
For Each SS In SSCollection
    If SS.Name = "mastSS" Then
        SSCollection.Item("mastSS").Delete
        Exit For
    End If
Next

'create a selection set
Set pubMastSS = ThisDrawing.SelectionSets.Add("mastSS")
'add only objects with the correct name to the selection set
pubMastSS.Select acSelectionSetAll, , , filtertype, filterdata

End Sub

Public Sub get_wireSS()
'Creates a selection set of all shield wire objects
'in the drawing (objects named "ltg_shield_wire").
'See pubwiress public variable

Dim SSCollection As AcadSelectionSets
Dim SS As AcadSelectionSet
Dim filtertype(0) As Integer
Dim filterdata(0) As Variant
Dim i As Integer

'set dxf data type to "object name"
filtertype(0) = 2
'set dxf data value
filterdata(0) = "ltg_shield_wire"

'search for existing selection set and delete it if found
Set SSCollection = ThisDrawing.SelectionSets
For Each SS In SSCollection
    If SS.Name = "wireSS" Then
        SSCollection.Item("wireSS").Delete
        Exit For
    End If
Next

'create a selection set
Set pubWireSS = ThisDrawing.SelectionSets.Add("wireSS")
'add only objects with the correct name to the selection set
pubWireSS.Select acSelectionSetAll, , , filtertype, filterdata

End Sub

Public Sub load_mast_data()
'loads mast attribute data into the mast listbox

Dim i As Integer
Dim mastArray() As Variant
Dim MastObj As AcadBlockReference
Dim MastAtt As Variant

'get the mastSS selection set
Call get_mastSS

'build array of attribute data from each mast in the selection set
If pubMastSS.Count > 0 Then
    For i = 0 To pubMastSS.Count - 1
        Set MastObj = pubMastSS.Item(i)
        MastAtt = MastObj.GetAttributes
        ReDim Preserve mastArray(6, i)
        'get mast ID
        mastArray(0, i) = MastAtt(0).TextString
        'get mast Height
        mastArray(1, i) = MastAtt(1).TextString
        'get wire1
        mastArray(2, i) = MastAtt(2).TextString
        'get wire2
        mastArray(3, i) = MastAtt(3).TextString
        'get wire3
        mastArray(4, i) = MastAtt(4).TextString
        'get wire4
        mastArray(5, i) = MastAtt(5).TextString
        'get wire5
        mastArray(6, i) = MastAtt(6).TextString
    Next
    With frmMain
        .cmbDeleteMast.Enabled = True
        .cmbIdentifyMast.Enabled = True
        .cmbEditMast.Enabled = True
    End With
Else
    'no masts were found
    ReDim mastArray(0, 0)
    mastArray(0, 0) = "No shield masts found"
    With frmMain
        .cmbEditMast.Enabled = False
        .cmbIdentifyMast.Enabled = False
        .cmbDeleteMast.Enabled = False
    End With
End If

'load data into mast listbox
With frmMain.lbxMasts
    .Column() = mastArray
    .ListIndex = 0
End With

End Sub

Public Sub load_wire_data()
'loads wire attribute data into the wire listbox

Dim i As Integer
Dim wireArray() As Variant
Dim WireObj As AcadBlockReference
Dim WireAtt As Variant

'get the mastSS selection set and check to make sure
'there are at least 2 masts in the drawing
Call get_mastSS
If pubMastSS.Count < 2 Then
    frmMain.cmbNewWire.Enabled = False
Else
    frmMain.cmbNewWire.Enabled = True
End If

'get the wireSS selection set
Call get_wireSS

'build array of attribute data from each wire in the selection set
If pubWireSS.Count > 0 Then
    For i = 0 To pubWireSS.Count - 1
        Set WireObj = pubWireSS.Item(i)
        WireAtt = WireObj.GetAttributes
        ReDim Preserve wireArray(3, i)
        'get wire ID
        wireArray(0, i) = WireAtt(0).TextString
        'get wire Height
        wireArray(1, i) = WireAtt(1).TextString
        'get wire mast1
        wireArray(2, i) = WireAtt(2).TextString
        'get wire mast2
        wireArray(3, i) = WireAtt(3).TextString
    Next
    With frmMain
        .cmbDeleteWire.Enabled = True
    End With
Else
    ReDim wireArray(0, 0)
    wireArray(0, 0) = "No shield wires found"
    With frmMain
        .cmbDeleteWire.Enabled = False
    End With
End If

'load data into wire listbox
With frmMain.lbxWires
    .Column() = wireArray
    .ListIndex = 0
End With

End Sub

Public Sub delete_mast()
'deletes the selected mast in the mast listbox and
'also deletes any shield wires attached to that mast

Dim MastObj As AcadBlockReference
Dim Mast1Obj As AcadBlockReference
Dim Mast2Obj As AcadBlockReference
Dim WireObj As AcadBlockReference
Dim MastAtt As Variant
Dim Mast1Att As Variant
Dim Mast2Att As Variant
Dim WireAtt As Variant
Dim response
Dim i As Integer
Dim a As Integer
Dim WireName As String

'get the mast object
Set MastObj = modFunctions.get_mast(frmMain.lbxMasts.Value)

'check for attached wires
MastAtt = MastObj.GetAttributes
For i = 2 To 6
    If MastAtt(i).TextString > "" Then
        response = MsgBox("Warning! All shield wires attached to this mast will be deleted.", vbOKCancel, "Delete Mast")
        'check if user wants to cancel
        If response = 1 Then
            Exit For
        Else
            Exit Sub
        End If
    End If
Next

'delete all attached wires
For i = 2 To 6
    'check for a value in the shield wire attribute
    If MastAtt(i).TextString > "" Then
        WireName = MastAtt(i).TextString
        'get wire object and attributes
        Set WireObj = modFunctions.get_wire(WireName)
        WireAtt = WireObj.GetAttributes
        'get wire's mast1 object and attributes
        Set Mast1Obj = modFunctions.get_mast(WireAtt(2).TextString)
        Mast1Att = Mast1Obj.GetAttributes
        'check to see if this is mastobj
        If Mast1Att(0).TextString <> MastAtt(0).TextString Then
            For a = 2 To 6
                If Mast1Att(a).TextString = WireName Then
                    'remove reference to deleted wire
                    Mast1Att(a).TextString = ""
                End If
            Next
        End If
        'get wire's mast2 object and attributes
        Set Mast2Obj = modFunctions.get_mast(WireAtt(3).TextString)
        Mast2Att = Mast2Obj.GetAttributes
        'check to see if this is mastobj
        If Mast2Att(0).TextString <> MastAtt(0).TextString Then
            For a = 2 To 6
                If Mast2Att(a).TextString = WireName Then
                    'remove reference to deleted wire
                    Mast2Att(a).TextString = ""
                End If
            Next
        End If
        'remove reference to deleted wire
        MastAtt(i).TextString = ""
        'delete wire
        WireObj.Delete
    End If
Next

'delete mast object
MastObj.Delete

'regenerate viewport
ThisDrawing.Regen acActiveViewport

'reload mast listbox
Call load_mast_data

'reload wire listbox
Call load_wire_data

End Sub

Public Sub delete_wire()
'deletes the selected wire in the mast listbox

Dim WireObj As AcadBlockReference
Dim WireAtt As Variant
Dim Mast1Obj As AcadBlockReference
Dim Mast2Obj As AcadBlockReference
Dim Mast1Att As Variant
Dim Mast2Att As Variant
Dim a As Integer
Dim WireName As String

'get the wire object
Set WireObj = modFunctions.get_wire(frmMain.lbxWires.Value)

'delete references to the wire
WireAtt = WireObj.GetAttributes
WireName = WireAtt(0).TextString
'get wire's mast1 object and attributes
Set Mast1Obj = modFunctions.get_mast(WireAtt(2).TextString)
Mast1Att = Mast1Obj.GetAttributes
For a = 2 To 6
    If Mast1Att(a).TextString = WireName Then
        'remove reference to deleted wire
        Mast1Att(a).TextString = ""
    End If
Next
'get wire's mast2 object and attributes
Set Mast2Obj = modFunctions.get_mast(WireAtt(3).TextString)
Mast2Att = Mast2Obj.GetAttributes
For a = 2 To 6
    If Mast2Att(a).TextString = WireName Then
        'remove reference to deleted wire
        Mast2Att(a).TextString = ""
    End If
Next

'delete wire object
WireObj.Delete

'regenerate viewport
ThisDrawing.Regen acActiveViewport

'reload wire listbox
Call load_wire_data

'reload mast listbox
Call load_mast_data

End Sub

Public Sub get_project_data()
'retrieves project data from the project data block
'and adds it to the main form

Dim dataObj As AcadBlockReference
Dim dataAtt As Variant
Dim datainspt(0 To 2) As Double

Call get_dataSS

'check to see if the data block exists
If pubDataSS.Count = 0 Then
    'set insertion point
    datainspt(0) = 0
    datainspt(1) = 0
    datainspt(2) = 0
    'insert data block
    Set dataObj = ThisDrawing.ModelSpace.InsertBlock(datainspt, pubBlockPath & "ltg_project_data.dwg", 1, 1, 1, 0)
Else
    Set dataObj = pubDataSS.Item(0)
End If

'get attributes
dataAtt = dataObj.GetAttributes
'project scale attribute
pubDWGScale = dataAtt(0).TextString
'project name attribute
pubProjectName = dataAtt(1).TextString
'project client attribute
pubClient = dataAtt(2).TextString

End Sub

Public Sub get_dataSS()
'Creates a selection set of project data objects
'in the drawing (objects named "ltg_project_data").
'See pubdatass public variable

Dim SSCollection As AcadSelectionSets
Dim SS As AcadSelectionSet
Dim filtertype(0) As Integer
Dim filterdata(0) As Variant
Dim i As Integer

'set dxf data type to "object name"
filtertype(0) = 2
'set dxf data value
filterdata(0) = "ltg_project_data"

'search for existing selection set and delete it if found
Set SSCollection = ThisDrawing.SelectionSets
For Each SS In SSCollection
    If SS.Name = "dataSS" Then
        SSCollection.Item("dataSS").Delete
        Exit For
    End If
Next

'create a selection set
Set pubDataSS = ThisDrawing.SelectionSets.Add("dataSS")
'add only objects with the correct name to the selection set
pubDataSS.Select acSelectionSetAll, , , filtertype, filterdata

End Sub

Public Sub write_project_data()
'writes project data from the main form to the
'project data block attributes

Dim dataAtt As Variant
Dim dataObj As AcadBlockReference

Call get_dataSS

Set dataObj = pubDataSS.Item(0)

'get attributes
dataAtt = dataObj.GetAttributes
'project scale attribute
dataAtt(0).TextString = frmMain.txbScale.Value
'project name attribute
dataAtt(1).TextString = frmMain.txbProjectName.Value
'project client attribute
dataAtt(2).TextString = frmMain.txbClient.Value

dataObj.Update

'update project data variables
Call get_project_data

frmMain.cmbProjectApply.Enabled = False
frmMain.cmbProjectReset.Enabled = False

End Sub

Public Sub reset_project_data()
'resets project data on the main form to the
'project data block attributes

Dim dataAtt As Variant
Dim dataObj As AcadBlockReference

Call get_dataSS

Set dataObj = pubDataSS.Item(0)

'get attributes
dataAtt = dataObj.GetAttributes
'project scale attribute
frmMain.txbScale.Value = dataAtt(0).TextString
'project name attribute
frmMain.txbProjectName.Value = dataAtt(1).TextString
'project client attribute
frmMain.txbClient.Value = dataAtt(2).TextString

frmMain.cmbProjectApply.Enabled = False
frmMain.cmbProjectReset.Enabled = False

End Sub

Public Sub insert_wire(Mast1Obj As AcadBlockReference, Mast2Obj As AcadBlockReference, WireID As String, WireHeight As Double)
'inserts the ltg_shield_wire block and fills in the
'ID and Height attributes

Dim WireObj As AcadBlockReference
Dim WireAtt As Variant
Dim wireInsAngle As Variant
Dim wireLength As Variant
Dim Mast1Att As Variant
Dim Mast2Att As Variant
Dim mast1loc(0 To 2) As Double
Dim mast2loc(0 To 2) As Double
Dim mast1ID As String
Dim mast2ID As String

'get fist mast coordinates
mast1loc(0) = Mast1Obj.InsertionPoint(0)
mast1loc(1) = Mast1Obj.InsertionPoint(1)
mast1loc(2) = Mast1Obj.InsertionPoint(2)
'get first mast ID attribute
Mast1Att = Mast1Obj.GetAttributes
mast1ID = Mast1Att(0).TextString

'get second mast coordinates
mast2loc(0) = Mast2Obj.InsertionPoint(0)
mast2loc(1) = Mast2Obj.InsertionPoint(1)
mast2loc(2) = Mast2Obj.InsertionPoint(2)
'get second mast ID attribute
Mast2Att = Mast2Obj.GetAttributes
mast2ID = Mast2Att(0).TextString

'get angle between masts (radians)
wireInsAngle = ThisDrawing.Utility.AngleFromXAxis(mast1loc, mast2loc)

'get distance between masts
wireLength = modFunctions.XYZDistance(mast1loc, mast2loc)

'insert wire block
Set WireObj = ThisDrawing.ModelSpace.InsertBlock(mast1loc, pubBlockPath & "ltg_shield_wire.dwg", wireLength, wireLength, wireLength, wireInsAngle)

'get wire attributes
WireAtt = WireObj.GetAttributes
'add wire ID to attribute
WireAtt(0).TextString = WireID
'add wire height to attribute
WireAtt(1).TextString = WireHeight
'add mast1 attribute
WireAtt(2).TextString = mast1ID
'add mast2 attribute
WireAtt(3).TextString = mast2ID

End Sub

Attribute VB_Name = "modVariables"
Option Explicit

Public pubFilePath As String
Public pubDWGScale As Double
Public pubDataLayout As AcadLayout
Public pubDataPath As String
Public pubBlockPath As String
Public pubMastSS As AcadSelectionSet
Public pubWireSS As AcadSelectionSet
Public pubDataSS As AcadSelectionSet
Public pubProjectName As String
Public pubClient As String

Public Sub set_variables()
pubFilePath = "C:\Users\hoo28948\OneDrive\BV\AutoCAD\VBA\Lightning\"
pubDataPath = "C:\Users\hoo28948\OneDrive\BV\AutoCAD\VBA\Lightning\Data\"
pubBlockPath = "C:\Users\hoo28948\OneDrive\BV\AutoCAD\VBA\Lightning\Blocks\"
End Sub
